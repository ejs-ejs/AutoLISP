;;;
;;; 
;;; A lot of command for switching layer by pattern
;;;  The early handy tools for drafting purposes
;;;  Have no real value in the BIM environment
;;;
;;; (c) ejs 1997 -2020
;;; The provided software will not suite any of your needs, will do any harm for your data. 
;;; Handle with care.
;;;

(defun c:0a ()
  (command "-layer" "t"	"*" "s"	"0" "f"	"*" "t"	"*_0a_*" "on" "*_0a_*"
	   "")
  (command "_.ucs" "r" "0a")
)
(defun c:-0a ()
  (command "-layer" "f" "*_0a_*" "")
)
(defun c:+0a ()
  (command "-layer" "t" "*_0a_*" "on" "*_0a_*" "")
)

(defun c:1a ()
  (command "-layer" "t"	"*" "s"	"0" "f"	"*" "t"	"*_1a_*" "on" "*_1a_*"
	   "")
  (command "_.ucs" "r" "1a")
)
(defun c:-1a ()
  (command "-layer" "f" "*_1a_*" "")
)
(defun c:+1a ()
  (command "-layer" "t" "*_1a_*" "on" "*_1a_*" "")
)

(defun c:2a ()
  (command "-layer" "t"	"*" "s"	"0" "f"	"*" "t"	"*_2a_*" "on" "*_2a_*"
	   "")
  (command "_.ucs" "r" "2a")
)
(defun c:-2a ()
  (command "-layer" "f" "*_2a_*" "")
)
(defun c:+2a ()
  (command "-layer" "t" "*_2a_*" "on" "*_2a_*" "")
)
(defun c:3a ()
  (command "-layer" "t"	"*" "s"	"0" "f"	"*" "t"	"*_3a_*" "on" "*_3a_*"
	   "")
  (command "_.ucs" "r" "3a")
)
(defun c:-3a ()
  (command "-layer" "f" "*_3a_*" "")
)
(defun c:+3a ()
  (command "-layer" "t" "*_3a_*" "on" "*_3a_*" "")
)
(defun c:4a ()
  (command "-layer" "t"	"*" "s"	"0" "f"	"*" "t"	"*_4a_*" "on" "*_4a_*"
	   "")
  (command "_.ucs" "r" "4a")
)
(defun c:-4a ()
  (command "-layer" "f" "*_4a_*" "")
)
(defun c:+4a ()
  (command "-layer" "t" "*_4a_*" "on" "*_4a_*" "")
)
(defun c:5a ()
  (command "-layer" "t"	"*" "s"	"0" "f"	"*" "t"	"*_5a_*" "on" "*_5a_*"
	   "")
  (command "_.ucs" "r" "5a")
)
(defun c:-5a ()
  (command "-layer" "f" "*_5a_*" "")
)
(defun c:+5a ()
  (command "-layer" "t" "*_5a_*" "on" "*_5a_*" "")
)
(defun c:ra ()
  (command "-layer" "t"	     "*"      "s"      "0"	"f"
	   "*"	    "t"	     "*_-1a_*"	       "on"	"*_-1a_*"
	   ""
	  )
  (command "_.ucs" "r" "ra")
)
(defun c:-ra ()
  (command "-layer" "f" "*_-1a_*" "")
)
(defun c:+ra ()
  (command "-layer" "t" "*_-1a_*" "on" "*_-1a_*" "")
)
(defun c:sta ()
  (command "-layer"  "t"       "*"	 "s"	   "0"	     "f"
	   "*"	     "t"       "*_stogas_*"	   "on"
	   "*_stogas_*"	       ""
	  )
  (command "_.ucs" "r" "sta")
)
(defun c:-sta ()
  (command "-layer" "f" "*_stogas_*" "")
)
(defun c:+sta ()
  (command "-layer" "t" "*_stogas_*" "on" "*_stogas_*" "")
)
(defun c:2d ()
  (command "-layer" "t"	"*" "s"	"0" "f"	"*" "t"	"*_2d" "on" "*_2d" "")
)
(defun c:3d ()
  (command "-layer" "t"	"*" "s"	"0" "f"	"*" "t"	"*_3d" "on" "*_3d" "")
)
(defun c:+2d ()
  (command "-layer" "t" "*_2d" "on" "*_2d" "")
)
(defun c:-2d ()
  (command "-layer" "f" "*_2d" "")
)
(defun c:+3d ()
  (command "-layer" "t" "*_3d" "on" "*_3d" "")
)
(defun c:-3d ()
  (command "-layer" "f" "*_3d" "")
)
(defun c:fas ()
  (command "-layer" "t"	"*" "s"	"0" "f"	"*" "t"	"*_fas*" "on" "*_fas*"
	   "")
				;(c:dducs)
)
(defun c:+fas ()
  (command "-layer" "t"	"*_fas*" "on" "*_fas*" "")
)

(defun c:-fas ()
  (command "-layer" "f"	"*_fas*" "")
)

(defun c:+pj ()
  (command "-layer" "t"	"*_pj*" "on" "*_pj*" "")
)

(defun c:-pj ()
  (command "-layer" "f"	"*_pj*" "")
)

(defun c:pj ()
  (command "-layer" "t"	"*" "s"	"0" "f"	"*" "t"	"a_pj*"	"on" "a_pj*" "")
					; (c:dducs)
)
(defun c:det ()
  (command "-layer" "t" "a_det_2d" "")
)
(defun c:-det ()
  (command "-layer" "f" "a_det_2d" "")
)

(defun c:gp ()
  (command "-layer" "t"	"*" "s"	"0" "f"	"*" "t"	"gp*" "on" "gp*" "")
)
(defun c:+gp ()
  (command "-layer" "t" "gp*" "on" "gp*" "")
)
(defun c:-gp ()
  (command "-layer" "f" "gp*" "")
)
