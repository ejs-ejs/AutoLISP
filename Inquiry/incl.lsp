(defun c:incl()
  (setq A (getpoint"\nPick first point")
	B (getpoint"\nPick second point")
	res (/ (abs (- (cadr A) (cadr B))) (abs (- (car A) (car B)) ))
	ans (strcat "Inclination: " (rtos res) " (" (rtos (* res 100)) " %)"))
  ;(print (strcat "\n" ans "\n"))
  (princ (strcat "\n" ans "\n"))
  (princ)
  )
